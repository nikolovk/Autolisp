;;;;; funkcia za naprava na spisak sas skalite na kartite
(defun s::startup ( / fp1 map ss num dwg-name)
   (setvar "FILEDIA" 0)
   (setvar "CMDDIA" 0)
   (setvar "SDI" 1)   
   (setq fp1 (open "number.txt" "r"))
     (setq num (atoi (read-line fp1)))
   (close fp1)
   (setq fp1 (open "maps.txt" "r"))
   (repeat num
      (setq dwg-name (read-line fp1))
   )
   (close fp1)
   (if (= dwg-name nil) 
       (progn
          (setvar "FILEDIA" 1)
          (setvar "CMDDIA" 1)
          (setvar "SDI" 0)
          (command ".quit")
        )
   )
   (cxf-new-auto dwg-name)
   (setq fp1 (open "number.txt" "w"))
      (setq num (+ num 1))
      (write-line (itoa num) fp1) 
   (close fp1)
   (command ".qsave")
   (command ".open" "cat.dwg")
)
