(defun menu-proverka-txt ( / )
  (c:check-txt-file)
  (print-spisyci)
  (broi-greshki)
  (textscr)
)

(defun podredeni-plosht-novi ( / sp-nov e1 e2)
  (c:check-txt-file)
  (setq sp-nov sp-novi)
  (setq sp-nov (vl-sort sp-nov '(lambda (e1 e2) (< (atoi (cadr e1)) (atoi (cadr e2))))))
  (print-sp-new sp-nov)
  (alert "OTVORI .spisyk ZA PODREDENI NOVI NOMERA")
)


(defun make-sp-part ( / a fp txt x num pl att red e1 e2 map-txt map-dwg len)
  \\ Pravi spisyk po txt fail
  ;; vzimame map-dwg - nomer na karta
  (setq map-dwg (getvar "DWGNAME"))
  ;(setq len (strlen map-dwg))
  (setq map-dwg (substr map-dwg 6 4))
  (setq map-dwg (remove-0 map-dwg))
  ;(alert map-dwg)
  (setq sp-txt nil)
  (while (= fp nil)
    (setq txt (getfiled	"Izberi tekstov fail s ploshti"
			"c:\\cat\\"
			"txt"
			4
	      )
    )
    (setq fp (open txt "r"))
  )
  (setq txt (read-line fp))
  (while (/= txt nil)
    (setq map-txt "")
    (setq x (substr txt 1 1))
    (setq txt (substr txt 2))
    (while (/= x "\,")
      (setq map-txt (strcat map-txt x))
      (setq x (substr txt 1 1))
      (setq txt (substr txt 2))
    )
    (setq map-txt (remove-space map-txt))
    ;(princ map-txt)
    (setq x (substr txt 1 1))
    (setq txt (substr txt 2))
    (setq num x)
    (while (/= x "\,")
      (setq x (substr txt 1 1))
      (setq txt (substr txt 2))
      (if (/= x "\,")
	(setq num (strcat num x))
      )
    )
    (setq num (remove-0 num))
    (setq x (substr txt 1 1))
    (setq txt (substr txt 2))
    (setq pl x)
    (if	(= pl "\,")
      (setq pl "0")
    )
    (while (/= x "\,")
      (setq x (substr txt 1 1))
      (setq txt (substr txt 2))
      (if (/= x "\,")
	(setq pl (strcat pl x))
      )
    )
    (setq pl (remove-space pl))
    (setq x (substr txt 1 1))
    (setq txt (substr txt 2))
    (setq att x)
    (while (/= x "\,")
      (setq x (substr txt 1 1))
      (setq txt (substr txt 2))
      (if (/= x "\,")
	(setq att (strcat att x))
      )
    )
    (setq txt (substr txt 2))
    (setq red (list num pl att txt))
    ;(princ red)
    (if (= map-txt map-dwg) (setq sp-txt (cons red sp-txt)))


    ;;;;;;;;;;;;;;;;;;;;;;;;;;;;;;;;;;
    (setq txt (read-line fp))
  )
  
  (close fp)
  (setq sp-txt (txt-sort sp-txt))
)

\\ Pravi tx fail s podredeni nomera
(defun make-tx-file (sp / fp txt-name red)
  (setq txt-name (substr (getvar "DWGNAME") 1 5))
  (setq txt-name (strcat (getvar "DWGPREFIX") txt-name ".tx"))
  (setq fp (open txt-name "a"))
  (setq red (car sp))
  (setq sp (cdr sp))
  (while red
    (write-line (strcat (car red) "-" (cadr red) "-" (caddr red) "-" (caddr (cdr red))) fp)
    (setq red (car sp))
    (setq sp (cdr sp))
  )
  (close fp)
)
(defun print-sp-new (sp / red)
  (setq name (substr (getvar "DWGNAME") 1 5))
  (setq name (strcat (getvar "DWGPREFIX") name ".spisyk"))
  (setq fp (open name "w"))
  (setq red (car sp))
  (setq sp (cdr sp))
  (write-line "SPISYK NOMERA:" fp)
  (while red
    (write-line (strcat (car red) "-" (cadr red) "-" (caddr red) "-" (caddr (cdr red))) fp)
    (setq red (car sp))
    (setq sp (cdr sp))
  )
  (close fp)
  (if (= sp-txt nil) (alert "PUSNI PROVERKA TXT"))
)


(defun c:check-txt-file ( / sp-part ss red el-txt sp-txt-orig num i red-orig sp-novi-orig sp-stari-orig
			 txt-name fp e1 e2 ent max-num)
  (setq sp-stari nil)
  (setq sp-novi nil)
  (make-sp-part)
  (setq max-num "99999")
  (setq ss (ssget "x" (list (cons 1 "MAX-NUM:*") (cons 8 "PLOSHT-XLS"))))
  (if ss (setq ent (entget (ssname ss 0))))
  (if ss (setq max-num (cdr (assoc 1 ent))))
  (if ss (setq max-num (substr max-num 9)))
  (if (not ss) (alert "LIPSVA MAX NUM"))
  (setq max-num (atoi max-num))
  (setq sp-txt-orig sp-txt)
  (setq ss (ssget "x" (list (cons 0 "TEXT") (cons 8 "*N-PART"))))
  (setq sp-part (make-spisyk-ss ss))
  (setq red (car sp-txt))
  (setq sp-txt (cdr sp-txt))
  (while red
    (setq el-txt (car red))
    (if (and (not (member el-txt sp-part)) (/= (caddr red) "Soppressa"))
      (setq sp-novi (cons red sp-novi))
    )
    (setq red (car sp-txt))
    (setq sp-txt (cdr sp-txt))
  )
  (setq num (car sp-part))
  (setq sp-part (cdr sp-part))
  (while (or (= num "STRADA") (= num "ACQUA"))
    (setq num (car sp-part))
    (setq sp-part (cdr sp-part))
  )
  (while num
    (setq i 0)
    (setq red-orig nil)
    (setq sp-txt sp-txt-orig)
    (setq red (car sp-txt))
    (setq sp-txt (cdr sp-txt))
    (while red
      (setq el-txt (car red))
      (if (= el-txt num) (setq i 1))
      (if (= el-txt num) (setq red-orig red))
      (setq red (car sp-txt))
      (setq sp-txt (cdr sp-txt))
      (if (= el-txt num) (setq red nil))
    )
    (if (and (= i 0) (or (< (atoi num) max-num) (> (atoi num) (+ max-num 200)))) (setq sp-stari (cons (list num "" "" "") sp-stari)))
    (if (= (caddr red-orig) "Soppressa") (setq sp-stari (cons red-orig sp-stari)))
    (setq num (car sp-part))
    (setq sp-part (cdr sp-part))
    (while (or (= num "STRADA") (= num "ACQUA"))
      (setq num (car sp-part))
      (setq sp-part (cdr sp-part))
    )
  )
  (setq sp-novi (txt-sort sp-novi))
  (setq sp-stari (txt-sort sp-stari))
  (setq sp-novi-orig sp-novi)
  (setq sp-stari-orig sp-stari)
  (setq txt-name (substr (getvar "DWGNAME") 1 5))
  (setq txt-name (strcat (getvar "DWGPREFIX") txt-name ".tx"))
  (setq fp (open txt-name "w"))
  (setq red (car sp-stari))
  (setq sp-stari (cdr sp-stari))
  (write-line "SPISYK NOMERA ZA IZTRIVANE" fp)
  (while red
    (write-line (strcat (car red) "-" (cadr red) "-" (caddr red) "-" (caddr (cdr red))) fp)
    (setq red (car sp-stari))
    (setq sp-stari (cdr sp-stari))
  )
  (setq red (car sp-novi))
  (setq sp-novi (cdr sp-novi))
  (write-line "SPISYK NOMERA ZA DOBAVIANE" fp)
  (while red
    (write-line (strcat (car red) "-" (cadr red) "-" (caddr red) "-" (caddr (cdr red))) fp)
    (setq red (car sp-novi))
    (setq sp-novi (cdr sp-novi))
  )
  
  (setq sp-novi sp-novi-orig)
  (setq sp-stari sp-stari-orig)
  (ocveti-spisyk-txt sp-stari "00")
  (setq sp-txt sp-txt-orig)
  (close fp)
)

;; PECHAT SPISYCI NA EKRANA BEZ PLOSHTI I INFO
(defun print-spisyci ( / sp red sp-tmp)
  (setq sp-tmp sp-stari)
  (setq red (car sp-tmp))
  (setq sp-tmp (cdr sp-tmp))
  (while red
    (setq sp (cons (car red) sp))
    (setq red (car sp-tmp))
    (setq sp-tmp (cdr sp-tmp))
  )
  (princ "\nSPISYK ZA IZTRIVANE:\n")
  (princ sp)
  (setq sp nil)
  (setq sp-tmp sp-novi)
  (setq red (car sp-tmp))
  (setq sp-tmp (cdr sp-tmp))
  (while red
    (setq sp (cons (car red) sp))
    (setq red (car sp-tmp))
    (setq sp-tmp (cdr sp-tmp))
  )
  (princ "\nSPISYK ZA DOBAVIANE:\n")
  (princ sp)
)

(defun ocveti-spisyk-txt ( sp tip / cviat txt ss sp-d )
  (setq ss (ssget "x" (list (cons 0 "TEXT") (cons 8 "*N-PART"))))
  (command "chprop" ss "" "c" "Bylayer" "")  
  (setq cviat "BYLAYER" txt "")
  (if (= tip "00") (setq cviat "88"))
  (setq sp-d sp-dup)
  (while sp-d
    (setq txt (strcat (car sp-d) "," txt))
    (setq sp-d (cdr sp-d))
  )
  (setq ss (ssget "x" (list (cons 0 "TEXT") (cons 1 txt) (cons 8 "*N-PART"))))
  (setq txt "")
  (if ss (command "chprop" ss "" "c" "80" ""))
  (while sp
    (setq txt (strcat (car (car sp)) "," txt))
    (setq sp (cdr sp))
  )
  (setq ss (ssget "x" (list (cons 0 "TEXT") (cons 1 txt) (cons 8 "*N-PART"))))
  (command "chprop" ss "" "c" cviat "")
)

;;Pokazva 00 posledovatelno
(defun c:zz (/ ss txt co ent x)
  (if (= sp-star nil) (setq sp-star sp-stari))
   (while (= ss nil)
    (setq x (car sp-star))
    (setq txt (car x))
    (setq sp-star (cdr sp-star))
    (setq ss (ssget "x" (list (cons 1 txt) (cons 8 "*N-PART"))))
  )
  (setq ent (entget (ssname ss 0)))
  (setq co (cdr (assoc 10 ent)))
  (command "zoom" "c" co "70")
  (prompt "\nNomer za iztrivane: ")
  (setvar "CMDECHO" 0)
  (princ x)
  (setvar "CMDECHO" 1)
  (setq txt (car x))
  (find-plosht-new txt)
)

;; POKAZVA NOVI NOMERA POSLEDOVATELNO
(defun c:nn (/ ss txt co ent x)
  (if (= sp-nov nil) (setq sp-nov sp-novi))
    (setq x (car sp-nov))
    (setq sp-nov (cdr sp-nov))
  (prompt "\nNomer za dobaviane: ")
  (setvar "CMDECHO" 0)
  (princ x)
  (setvar "CMDECHO" 1)
)

(defun find-plosht-new (txt     / sp-tmp el ent     plosht txt	   pl-el
			sp-eq ss y
		       )
  (setq ss (ssget "x" (list (cons 1 txt) (cons 8 "*N-PART"))))
  (setq ent (entget (ssname ss 0)))
  (setq co (cdr (assoc 10 ent)))
  (setq co (list 10 (car co) (- (cadr co) 1) (caddr co)))
  (setq ss (ssget "x" (list co (cons 8 "*PLOSHT"))))
  (setq ent (entget (ssname ss 0)))
  (setq plosht  (cdr (assoc 1 ent)))
  (setq plosht (atof plosht))
;;; tyrsi cen s takava plosht
  (setq sp-tmp sp-novi)
  (while sp-tmp
    (setq el (car sp-tmp))
    (setq pl-el (atoi (cadr el)))
    (if	(and (< pl-el (* plosht 1.1)) (> pl-el (* plosht 0.9)))
      (setq sp-eq (cons el sp-eq))
    )
    (setq sp-tmp (cdr sp-tmp))
  )
  (princ "\nParceli CEN s blizka plosht:\n")
  (princ sp-eq)
  (textscr)
)


(defun txt-sort ( sp / e1 e2 red sp-num sp-x sp-sort)
  (setq sp-num nil)
  (setq sp (vl-sort sp '(lambda (e1 e2) (< (car e1) (car e2)))))
  (setq red (car sp))
  (setq sp (cdr sp))
  (while red
    (if (/= (atoi (car red)) 0)
      (setq sp-num (cons red sp-num))
      (setq sp-x (cons red sp-x))
    )    
    (setq red (car sp))
    (setq sp (cdr sp))
  )
  (if sp-num (setq sp-num (vl-sort sp-num '(lambda (e1 e2) (< (atoi (car e1)) (atoi (car e2)))))))
  ;(princ sp-num)
  (if sp-x (setq sp-x (vl-sort sp-x '(lambda (e1 e2) (> (car e1) (car e2))))))
  ;(princ sp-x)
  (setq red (car sp-x))
  (setq sp-x (cdr sp-x))
  (while red
    (setq sp-num (cons red sp-num))
    (setq red (car sp-x))
    (setq sp-x (cdr sp-x))
  )
  (setq sp-sort sp-num)
)

(defun c:moz-work ( / )
  (command "-layer" "on" "*" "t" "*" "u" "*" "")
  (c:co-byl)
  (command "-layer" "lo" "*ORIGINAL,*PLOSHT*" "")
)

(defun max-num ( / max-num pt)
  (setq max-num nil)
  (setq sp-star nil)
  (command "-layer" "on" "*" "t" "*" "u" "*" "")
  (setvar "clayer" "PLOSHT-XLS")
  (initget 7)
  (setq max-num (getreal "Vavedi nai goliam nomer:"))
  (setq pt (getpoint "\nPosochi tochka za vmakvane na NOMER: "))
  (command "_text" pt 500 0 (strcat "MAX-NUM:" (rtos max-num 2 0)))
  (command "-layer" "m" "RASTER" "")
  (command "-layer" "lo" "*ORIGINAL,*PLOSHT*" "")
)

;; Tyrsi iztriti nomera ot dwg, koito ne sa 00
(defun c:check-del-num-new ( / sp-orig sp-part sp-pa el-orig el-part sp-new x y sp-00-tmp z sp-A)
  (setvar "CMDECHO" 0)
  (c:check-txt-file)
  (setq ss (ssget "x" (list (cons 0 "TEXT") (cons 8 "*ORIGINAL"))))
  (if ss
    (setq sp-orig (make-spisyk-ss ss))
    (alert "LIPSVAT ORIGINAL")
  )
  (if (= sp-novi nil) (alert "PUSNI PROVERKA TXT"))
  (setq sp-A sp-novi)
  (while (setq z (car (car sp-A)))
    (setq sp-00-tmp (cons z sp-00-tmp))
    (setq sp-A (cdr sp-A))
  )
  (setq ss (ssget "x" (list (cons 0 "TEXT") (cons 8 "*N-PART"))))
  (setq sp-part (make-spisyk-ss ss))
  (while sp-orig
    (setq el-orig (car sp-orig))
    (setq sp-orig (cdr sp-orig))
    (if sp-00-tmp (setq x (tyrsi-el el-orig sp-00-tmp)))
    (setq y (tyrsi-el el-orig sp-part))
    (if (and (/= x 0) (= y 0)) (setq sp-new (cons el-orig sp-new)))
  )
  (if sp-new
    (progn
      (setq sp-new (vl-sort sp-new '<))
      (princ "Iztriti nomera ot dwg, koito ne sa za IZTRIVANE\n")
      (princ sp-new)
    )
    (princ "Niama iztriti nomera")
  )
  (setvar "CMDECHO" 1)
  (textscr)
)


;; Tyrsi VSICHKI iztriti nomera ot dwg
(defun c:check-del-orig ( / sp-orig sp-part sp-pa el-orig el-part sp-new x y sp-00-tmp z sp-A)
  (setvar "CMDECHO" 0)
  (setq ss (ssget "x" (list (cons 0 "TEXT") (cons 8 "*ORIGINAL"))))
  (if ss
    (setq sp-orig (make-spisyk-ss ss))
    (alert "LIPSVAT ORIGINAL")
  )
  (setq ss (ssget "x" (list (cons 0 "TEXT") (cons 8 "*N-PART"))))
  (setq sp-part (make-spisyk-ss ss))
  (while sp-orig
    (setq el-orig (car sp-orig))
    (setq sp-orig (cdr sp-orig))
    (setq y (tyrsi-el el-orig sp-part))
    (if (= y 0) (setq sp-new (cons el-orig sp-new)))
  )
  (if sp-new
    (progn
      (setq sp-new (vl-sort sp-new '<))
      (princ "SPISYK NA VSICHKI IZTRITI NOMERA:\n")
      (princ sp-new)
    )
    (princ "Niama iztriti nomera")
  )
  (setvar "CMDECHO" 1)
  (textscr)
)
;; Tyrsi VSICHKI dobaveni nomera ot dwg
(defun c:check-dobaveni-all ( / sp-orig sp-part sp-pa el-orig el-part sp-new x y sp-00-tmp z sp-A)
  (setvar "CMDECHO" 0)
  (setq ss (ssget "x" (list (cons 0 "TEXT") (cons 8 "*ORIGINAL"))))
  (if ss
    (setq sp-orig (make-spisyk-ss ss))
    (alert "LIPSVAT ORIGINAL")
  )
  (setq ss (ssget "x" (list (cons 0 "TEXT") (cons 8 "*N-PART"))))
  (setq sp-part (make-spisyk-ss ss))
  (while sp-part
    (setq el-part (car sp-part))
    (setq sp-part (cdr sp-part))
    (setq y (tyrsi-el el-part sp-orig))
    (if (= y 0) (setq sp-new (cons el-part sp-new)))
  )
  (if sp-new
    (progn
      (setq sp-new (vl-sort sp-new '<))
      (princ "SPISYK NA VSICHKI DOBAVENI NOMERA:\n")
      (princ sp-new)
    )
    (princ "Niama dobaveni nomera")
  )
  (setvar "CMDECHO" 1)
  (textscr)
)


;; Tyrsi dobaveni nomera v dwg, koito ne sa CEN
(defun c:check-new-num-new ( / sp-orig sp-part sp-pa el-orig el-part sp-new x y sp-00-tmp )
  (setvar "CMDECHO" 0)
  (c:check-txt-file)
  (setq ss (ssget "x" (list (cons 0 "TEXT") (cons 8 "*ORIGINAL"))))
  (if ss
    (setq sp-orig (make-spisyk-ss ss))
    (alert "LIPSVAT ORIGINAL")
  )
  (if (= sp-stari nil)  (alert "PUSNI PROVERKA TXT"))
  (setq ss (ssget "x" (list (cons 0 "TEXT") (cons 8 "*N-PART"))))
  (setq sp-part (make-spisyk-ss ss))
  (while sp-stari
    (setq el-part (car (car sp-stari)))
    (setq sp-stari (cdr sp-stari))
    (setq y (tyrsi-el el-part sp-orig))
    (if (= y 0) (setq sp-new (cons el-part sp-new)))
  )
  (if sp-new
    (progn
      (setq sp-new (vl-sort sp-new '<))
      (princ "Dobaveni nomera v dwg, koito ne sa DOBAVIANE\n")
      (princ sp-new)
    )
    (princ "Niama dobaveni nomera")
  )
  (setvar "CMDECHO" 1)
  (textscr)
)

;; 
(defun broi-greshki ( / ss sp-orig sp-part sp-tx red broi-obshto broi-ostanali broi-popraveni)
 (setq broi-obshto 0)
 (setq broi-ostanali 0)
 (setq broi-popraveni 0)
 (setq ss (ssget "x" (list (cons 0 "TEXT") (cons 8 "*ORIGINAL"))))
 (if ss
    (setq sp-orig (make-spisyk-ss ss))
    (alert "LIPSVAT ORIGINAL")
 )
 (setq ss (ssget "x" (list (cons 0 "TEXT") (cons 8 "*N-PART"))))
  (setq sp-part (make-spisyk-ss ss))
  (setq sp-tx sp-txt)
  (setq red (car sp-tx))
  (setq sp-tx (cdr sp-tx))
  (while red
    (if (and (not (member (car red) sp-orig)) (/= (caddr red) "Soppressa")) (setq broi-obshto (+ broi-obshto 1)))
    (if (and (not (member (car red) sp-part)) (/= (caddr red) "Soppressa")) (setq broi-ostanali (+ broi-ostanali 1)))
    (setq red (car sp-tx))
    (setq sp-tx (cdr sp-tx))
  )
  (setq broi-popraveni (- broi-obshto broi-ostanali))
  (princ (strcat "\nOBSHTO NOMERA ZA DOBAVIANE: " (itoa broi-obshto)))
  (princ (strcat "\nPOPRAVENI NOMERA: " (itoa broi-popraveni)))
  (princ (strcat "\nOSTANALI NOMERA ZA DOBAVIANE: " (itoa broi-ostanali)))
  (textscr)
)



(defun find-plosht-txt (    / sp-tmp el ent     plosht txt	   pl-el
			sp-eq
		       )
  (while (= el nil)
    (print "Izberi text za plosht:")
    (setq el (ssget))
    (setq ent (entget (ssname el 0)))
    (setq plosht  (cdr (assoc 1 ent)))
    (setq plosht (atof plosht))
  )
;;; tyrsi cen s takava plosht
  (setq sp-tmp sp-novi)
  (while sp-tmp
    (setq el (car sp-tmp))
    (setq pl-el (atoi (cadr el)))
    (if	(and (< pl-el (* plosht 1.1)) (> pl-el (* plosht 0.9)))
      (setq sp-eq (cons el sp-eq))
    )
    (setq sp-tmp (cdr sp-tmp))
  )
  (princ "\nParceli CEN s blizka plosht:\n")
  (princ sp-eq)
  (textscr)
)


;; selektirame 00 parceli i tyrsim syotvetstvashti CEN po plosht
(defun c:fp ( / )
  (find-plosht-txt)
)
