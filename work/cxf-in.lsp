(defun make-dwg-txt ( / laylst flag laynam x dwg y fp dwg-name ss1)
  (setvar "CMDECHO" 0)
  (setvar "FILEDIA" 0)
  (setq ss1 nil)
  (command "-layer" "s" "0" "u" "*" "")
  
  (command "-purge" "a" "*" "n")
  (setq ss1 (ssget "X" '(
    (-4 . "<AND")
    (-4 . "<NOT")
    (8 . "0*")
    (-4 . "NOT>")
    (-4 . "<NOT")
    (8 . "PLOSHT-XLS")
    (-4 . "NOT>")
    (-4 . "AND>")
  )))
  (if ss1
    (progn
      (alert "OBEKTI V GRESHEN SLOI!!!!!")
      (setvar "FILEDIA" 1)
      (setvar "CMDECHO" 1)
      (exit)
    )
  )  
  (setq dwg (substr (getvar "DWGNAME") 1 5))
  (setq laylst nil)
  (setq flag T)
  (while (/= (setq x (tblnext "LAYER" flag)) nil)
    (setq flag nil)
    (setq laynam (cdr (assoc 2 x)))
    (if (and (/= laynam "0") (/= laynam "PLOSHT-XLS")) (setq laylst (cons laynam laylst)))
  )
  (setq laylst (acad_strlsort laylst))
  ;(princ laylst)
  (setq x (car laylst))
  (setq laylst (cdr laylst))
  (setq y nil)
  (setq fp (open (strcat (getvar "DWGPREFIX") "dwg.txt") "w"))
  (while (/= x "1")
    (setq y x)
    (setq dwg-name (strcat dwg (substr x 1 6) ".dwg"))
    (write-line dwg-name fp)
    (while (= (substr x 1 6) (substr y 1 6))
      (setq x (car laylst))
      (setq laylst (cdr laylst))
      (if (= x nil) (setq x "1"))
    )
    (princ x)
  )
  (close fp)
  (setvar "CMDECHO" 1)
  (setvar "FILEDIA" 1)
)
      


(defun c:dwg-out ( / fp dwg-name xx all-la )
  (setvar "CMDECHO" 0)
  (setvar "FILEDIA" 0)
  (command "-layer" "on" "*" "t" "*" "u" "*" "")
  (c:del-plosht)
  (make-dwg-txt)
  (setq fp (open (strcat (getvar "DWGPREFIX") "dwg.txt") "r"))
  (setq dwg-name (read-line fp))
  (while (/= dwg-name nil)
    (setq xx (strcat "C:\\cat\\gotovi\\" dwg-name))
    (setq dwg-name (substr dwg-name 6 6))
    (setq all-la (strcat dwg-name "*"))
    (setq cntr 0 ss1 nil)
    (setq ss1 (ssget "X" (list (cons 8 all-la))))
    (repeat (sslength ss1)
      (setq la-name (cdr (assoc 8 (entget (ssname ss1 cntr)))))
      (if (= (substr la-name 1 1) "0")
          (command "-rename" "la" la-name (substr la-name 8))
      )
      (setq cntr (1+ cntr))
    )
    (command "-wblock" xx "" "0,0" ss1 "")
    (command "-purge" "a" "*" "n")
    (setq dwg-name (read-line fp))
  ) 
  (setvar "CMDECHO" 1) 
  (setvar "FILEDIA" 1)
)



(defun c:dwg-ins ( / fp fp1 dwg-name xx ss1 la-name cntr sup sp)
  (command "-layer" "m" "PLOSHT" "c" "140" "" "")
  (setvar "CMDECHO" 0)
  (setq fp (open "C:\\cat\\mozaika\\dwg.txt" "r"))
  (setq dwg-name (read-line fp))
  (while (/= dwg-name nil)
    (command "-layer" "m" "PLOSHT" "c" "140" "" "")
    (setq xx (strcat "*C:\\cat\\mozaika\\" dwg-name))
    (setq sup (strcat "C:\\cat\\mozaika\\" (substr dwg-name 1 11) ".sup"))
    (setq dwg-name (substr dwg-name 6 6))
    (command "-insert" xx "0,0" "" "")
    (princ sup)
    (setq fp1 (open sup "r"))
    (if fp1
      (progn
	(setq sp (read-sup fp1))
	(write-sup sp "N-PART" "PLOSHT")
	(close fp1)
      )
    )
    (setq ss1 (ssget "X" '(
      (-4 . "<NOT")
      (8 . "0*")
      (-4 . "NOT>")
    )))
    (setq cntr 0 la-list nil)
    (repeat (sslength ss1)
      (setq la-name (cdr (assoc 8 (entget (ssname ss1 cntr)))))
      (if (/= (substr la-name 1 1) "0")
          (command "-rename" "la" la-name (strcat dwg-name "-" la-name))
      )
      (setq cntr (1+ cntr))
    )
    (setq dwg-name (read-line fp))
  )
  (setq ss (ssget "x" (list (cons 0 "TEXT") (cons 8 "*PLOSHT"))))
  (command "move" ss "" "0,0" "0,-1")
  (command "-layer" "s" "0" "lo" "*ORIGINAL" "")
  (setvar "CMDECHO" 1)
)



(defun c:write-sup-map ( / fp map)
  (command "-layer" "m" "PLOSHT" "c" "140" "" "")
  (while (= fp nil)
    (setq map (getfiled "Select a SUP file" "c:\\cat\\" "sup" 4))
    (setq fp (open map "r"))
  )
  (setq sp (read-sup fp))
  (write-sup sp "N-PART" "PLOSHT")
  (close fp)
  (setq ss (ssget "x" (list (cons 0 "TEXT") (cons 8 "*PLOSHT"))))
  (command "move" ss "" "0,0" "0,-1")
)


(defun cxf-new-auto	( karta / txt map la map1 xx)
  (setvar "CMDECHO" 0)
  (command "-layer" "t" "*" "on" "*" "")
  (command "-osnap" "OFF")
  (command "snap" "OFF")
  (command "ortho" "OFF")
  (setq xx (strcat "C:\\cat\\etap0\\" karta ".cxf"))
  (setq fp (open xx "r"))
  (setq txt (read-line fp))
  (setq map (read-line fp))
  (setq map (remove-space map))
  (setq map1 (strcat "C:\\cat\\etap0\\" map))
  (princ map1)
  (setvar "FILEDIA" 0)  
  (command "saveas" "" map1)
  (setvar "FILEDIA" 1)
  
  (setq scala (read-line fp))

  (while (eq (substr scala 1 1) " ")
    (setq scala (substr scala 2))
  )
  (setq scala (* (atof scala) 0.0001))
  (setq txt (read-line fp))
  (setq txt (remove-space txt))
  (while (/= txt "EOF" txt nil)

    (cond ((= txt "BORDO")
	   (draw-bordo)
	  )
	  ((= (substr txt 1 5) "TESTO")
	   (progn
	     (setq la (substr txt 1 5))
	     (if (= (substr txt 6 1) "\\")
	       (setq la "TESTO-OUT")
	     )
	     (draw-txt la)
	   )
	  )
	  ((= (substr txt 1 7) "SIMBOLO")
	   (progn
	     (setq la (substr txt 1 7))
	     (if (= (substr txt 8 1) "\\")
	       (setq la "SIMBOLO-OUT")
	     )
	     (draw-sim la)
	   )
	  )
	  ((= (substr txt 1 5) "LINEA")
	   (progn
	     (setq la (substr txt 1 5))
	     (if (= (substr txt 6 1) "\\")
	       (setq la "LINEA-OUT")
	     )
	     (draw-line la)
	   )
	  )
    	  ((= (substr txt 1 9) "DIVIDENTI")
	   (progn
	     (setq la (substr txt 1 9))
	     (draw-div la)
	   )
	  )
	  ((= (substr txt 1 9) "FIDUCIALE")
	   (progn
	     (setq la (substr txt 1 9))
	     (if (= (substr txt 10 1) "\\")
	       (setq la "FIDUCIALE-OUT")
	     )
	     (draw-fidu la)
	   )
	  )
	  ((= (substr txt 1 8) "LIBRETTO")
	   (draw-lib)
	  )
	  ((= (substr txt 1 18) "RIFERIMENTO_RASTER")
	   (draw-raster)
	  )
	  ((= (substr txt 1 9) "CENTROIDE")
	   (progn
	     (setq la (substr txt 1 9))
	     (draw-cntr la)
	   )
	  )	  
	  (t nil)
    )    
    (setq txt (read-line fp))
    (if	txt
      (setq txt (remove-space txt))
    )
  )
  (close fp)
  (setq fp nil)
  (setq scala (* scala 10))
  (setvar "FILEDIA" 0)  
  (command "saveas" "" dwg-name)
  (setvar "FILEDIA" 1)
  (cxf-start-new)
  (c:del-short)
  (original)
  (command "zoom" "e")
  (setvar "CMDECHO" 1)
)




(defun c:cxf-new	(/ txt map la map1)
  (setvar "CMDECHO" 0)
  (command "-layer" "t" "*" "on" "*" "")
  (command "-osnap" "OFF")
  (command "snap" "OFF")
  (command "ortho" "OFF")
  (while (= fp nil)
    (setq map (getfiled "Select a CXF file" "c:\\cat\\" "cxf" 4))
    (setq fp (open map "r"))
  )
  (setq txt (read-line fp))
  (setq map (read-line fp))
  (setq map (remove-space map))
  (setq map1 (strcat "C:\\cat\\etap0\\" map))  
  (setvar "FILEDIA" 0)  
  (command "saveas" "" map1)
  (setvar "FILEDIA" 1)
  
  (setq scala (read-line fp))

  (while (eq (substr scala 1 1) " ")
    (setq scala (substr scala 2))
  )
  (setq scala (* (atof scala) 0.0001))
  (setq txt (read-line fp))
  (setq txt (remove-space txt))
  (while (/= txt "EOF" txt nil)

    (cond ((= txt "BORDO")
	   (draw-bordo)
	  )
	  ((= (substr txt 1 5) "TESTO")
	   (progn
	     (setq la (substr txt 1 5))
	     (if (= (substr txt 6 1) "\\")
	       (setq la "TESTO-OUT")
	     )
	     (draw-txt la)
	   )
	  )
	  ((= (substr txt 1 7) "SIMBOLO")
	   (progn
	     (setq la (substr txt 1 7))
	     (if (= (substr txt 8 1) "\\")
	       (setq la "SIMBOLO-OUT")
	     )
	     (draw-sim la)
	   )
	  )
	  ((= (substr txt 1 5) "LINEA")
	   (progn
	     (setq la (substr txt 1 5))
	     (if (= (substr txt 6 1) "\\")
	       (setq la "LINEA-OUT")
	     )
	     (draw-line la)
	   )
	  )
    	  ((= (substr txt 1 9) "DIVIDENTI")
	   (progn
	     (setq la (substr txt 1 9))
	     (draw-div la)
	   )
	  )
	  ((= (substr txt 1 9) "FIDUCIALE")
	   (progn
	     (setq la (substr txt 1 9))
	     (if (= (substr txt 10 1) "\\")
	       (setq la "FIDUCIALE-OUT")
	     )
	     (draw-fidu la)
	   )
	  )
	  ((= (substr txt 1 8) "LIBRETTO")
	   (draw-lib)
	  )
	  ((= (substr txt 1 18) "RIFERIMENTO_RASTER")
	   (draw-raster)
	  )
	  ((= (substr txt 1 9) "CENTROIDE")
	   (progn
	     (setq la (substr txt 1 9))
	     (draw-cntr la)
	   )
	  )	  
	  (t nil)
    )    
    (setq txt (read-line fp))
    (if	txt
      (setq txt (remove-space txt))
    )
  )
  (close fp)
  (setq fp nil)
  (setq scala (* scala 10))
  (setvar "FILEDIA" 0)  
  (command "saveas" "" dwg-name)
  (setvar "FILEDIA" 1)
  (cxf-start-new)
  (c:del-short)
  (original)
  (command "zoom" "e")
  (setvar "CMDECHO" 1)
)


(defun c:cxf-in (/ txt map la)
  (setvar "CMDECHO" 0)
  (command "-layer" "t" "*" "on" "*" "")
  (command "-osnap" "OFF")
  (command "snap" "OFF")
  (command "ortho" "OFF")
  (while (= fp nil)
    (setq map (getfiled "Select a CXF file" "c:\\cat\\" "cxf" 4))
    (setq fp (open map "r"))
  )
  (setq txt (read-line fp))
  (setq map (read-line fp))
  (setq map (remove-space map))
  (setq scala (read-line fp))

  (while (eq (substr scala 1 1) " ")
    (setq scala (substr scala 2))
  )
  (setq scala (* (atof scala) 0.0001))
  (setq txt (read-line fp))
  (setq txt (remove-space txt))
  (while (/= txt "EOF")

    (cond ((= txt "BORDO")
	   (draw-bordo)
	  )
	  ((= (substr txt 1 5) "TESTO")
	   (progn
	     (setq la (substr txt 1 5))
	     (if (= (substr txt 6 1) "\\")
	       (setq la "TESTO-OUT")
	     )
	     (draw-txt la)
	   )
	  )
	  ((= (substr txt 1 7) "SIMBOLO")
	   (progn
	     (setq la (substr txt 1 7))
	     (if (= (substr txt 8 1) "\\")
	       (setq la "SIMBOLO-OUT")
	     )
	     (draw-sim la)
	   )
	  )
	  ((= (substr txt 1 5) "LINEA")
	   (progn
	     (setq la (substr txt 1 5))
	     (if (= (substr txt 6 1) "\\")
	       (setq la "LINEA-OUT")
	     )
	     (draw-line la)
	   )
	  )
;;;;;	  ((= (substr txt 1 9) "DIVIDENTI")
;;;;	   (progn
;;;;	     (setq la (substr txt 1 9))
;;;;	     (draw-div la)
;;;;	   )
;;;;	  )
	  ((= (substr txt 1 9) "FIDUCIALE")
	   (progn
	     (setq la (substr txt 1 9))
	     (if (= (substr txt 10 1) "\\")
	       (setq la "FIDUCIALE-OUT")
	     )
	     (draw-fidu la)
	   )
	  )
	  ((= (substr txt 1 8) "LIBRETTO")
	   (draw-lib)
	  )
	  ((= (substr txt 1 18) "RIFERIMENTO_RASTER")
	   (draw-raster)
	  )
	  ((= (substr txt 1 9) "CENTROIDE")
	   (progn
	     (setq la "N-PART")
	     (draw-cntr la)
	   )
	  )	  
	  (t nil)
    )    
    (setq txt (read-line fp))
    (if	txt
      (setq txt (remove-space txt))
    )
  )
  (close fp)
  (setq fp nil)
  (setq scala (* scala 10))
  (cxf-start)
  (c:del-short)
  (command "zoom" "e")
  (setvar "CMDECHO" 1)
)





(defun c:cxf-ins	(/ txt map la)
  (setvar "CMDECHO" 0)
  (command "-layer" "t" "*" "on" "*" "")
  (command "-osnap" "OFF")
  (command "snap" "OFF")
  (command "ortho" "OFF")
  (while (= fp nil)
    (setq map (getfiled "Select a CXF file" "c:\\cat\\" "cxf" 4))
    (setq fp (open map "r"))
  )
  (setq txt (read-line fp))
  (setq map (read-line fp))
  (setq map (remove-space map))
  (setq scala (read-line fp))

  (while (eq (substr scala 1 1) " ")
    (setq scala (substr scala 2))
  )
  (setq scala (* (atof scala) 0.0001))
  (setq txt (read-line fp))
  (setq txt (remove-space txt))
  (while (/= txt "EOF")

    (cond ((= txt "BORDO")
	   (draw-bordo)
	  )
	  ((= (substr txt 1 5) "TESTO")
	   (progn
	     (setq la (substr txt 1 5))
	     (if (= (substr txt 6 1) "\\")
	       (setq la "TESTO-OUT")
	     )
	     (draw-txt la)
	   )
	  )
	  ((= (substr txt 1 7) "SIMBOLO")
	   (progn
	     (setq la (substr txt 1 7))
	     (if (= (substr txt 8 1) "\\")
	       (setq la "SIMBOLO-OUT")
	     )
	     (draw-sim la)
	   )
	  )
	  ((= (substr txt 1 5) "LINEA")
	   (progn
	     (setq la (substr txt 1 5))
	     (if (= (substr txt 6 1) "\\")
	       (setq la "LINEA-OUT")
	     )
	     (draw-line la)
	   )
	  )
;;;;;	  ((= (substr txt 1 9) "DIVIDENTI")
;;;;	   (progn
;;;;	     (setq la (substr txt 1 9))
;;;;	     (draw-div la)
;;;;	   )
;;;;	  )
	  ((= (substr txt 1 9) "FIDUCIALE")
	   (progn
	     (setq la (substr txt 1 9))
	     (if (= (substr txt 10 1) "\\")
	       (setq la "FIDUCIALE-OUT")
	     )
	     (draw-fidu la)
	   )
	  )
	  ((= (substr txt 1 8) "LIBRETTO")
	   (draw-lib)
	  )
	  ((= (substr txt 1 18) "RIFERIMENTO_RASTER")
	   (draw-raster)
	  )
	  ((= (substr txt 1 9) "CENTROIDE")
	   (progn
	     (setq la "N-PART")
	     (draw-cntr la)
	   )
	  )	  
	  (t nil)
    )    
    (setq txt (read-line fp))
    (if	txt
      (setq txt (remove-space txt))
    )
  )
  (close fp)
  (setq fp nil)
  (setq scala (* scala 10))
  (setvar "FILEDIA" 0)  
  (command "saveas" "" dwg-name)
  (setvar "FILEDIA" 1)
  (cxf-start)
  (c:del-short)
  (command "zoom" "e")
  (setvar "CMDECHO" 1)
)



(defun DRAW-PLINE (pts /)
  (command "_PLINE")
  (mapcar 'command pts)
  (command "")
)

(defun DRAW-PLINE-C (pts /)
  (command "_PLINE")
  (mapcar 'command pts)
  (command "C")
)
(defun remove-space (txt / len tx)
  (setq len (strlen txt))
  (while (and (= (substr txt len 1) " ") (/= len 1))
    (setq txt (substr txt 1 (- len 1)))
    (setq len (strlen txt))
  )
  (while (and (= (substr txt 1 1) " ") (/= len 1))
    (setq txt (substr txt 2))
    (setq len (strlen txt))
  )
  (setq tx txt)
)

(defun remove-0 (txt / len tx)
  (setq len (strlen txt))
  (while (= (substr txt 1 1) "0")
    (setq txt (substr txt 2))
    (setq len (strlen txt))
  )
  (setq tx txt)
)

(defun draw-bordo (/	    num	     num_h    num_ang  pt1x
		   pt1y	    pt2x     pt2y     pt1      pt2
		   pol_ins  vert     br_vert_ins       x
		   ptlist_ins i
		  )
  (setq num (read-line fp))
  (setq num (remove-space num))
  (setq num_h (read-line fp))
  (if (= num_h "   0")
    (setq num_h "  18")
  )
  (if (and (/= num_h "  18") (/= num_h "  12"))
    (setq num_h "18")
  )
  (while (eq (substr num_h 1 1) " ")
    (setq num_h (substr num_h 2))
  )
  (setq num_ang (read-line fp))
  (while (eq (substr num_ang 1 1) " ")
    (setq num_ang (substr num_ang 2))
  )
  (setq pt1x (read-line fp))
  (while (eq (substr pt1x 1 1) " ")
    (setq pt1x (substr pt1x 2))
  )
  (setq pt1y (read-line fp))
  (while (eq (substr pt1y 1 1) " ")
    (setq pt1y (substr pt1y 2))
  )
  (setq pt1 (list (atof pt1x) (atof pt1y)))
  (setq pt2x (read-line fp))
  (while (eq (substr pt2x 1 1) " ")
    (setq pt2x (substr pt2x 2))
  )
  (setq pt2y (read-line fp))
  (while (eq (substr pt2y 1 1) " ")
    (setq pt2y (substr pt2y 2))
  )
  (setq pt2 (list (atof pt2x) (atof pt2y)))
  (setq len (strlen num))
  (if (not (equal pt1 pt2))
    (progn
      (setvar "CLAYER" "LINEA-P")
      (if (= (substr num len 1) "+")
	(setvar "CLAYER" "LINEA-E")
      )
      (if (and (= len 11) (/= (substr num len 1) " "))
	(setvar "CLAYER" "LINEA-C")
      )
      (command "_line" pt2 pt1 "")
    )
  )
  (setvar "CLAYER" "N-PART")
  ;(setvar "CECOLOR" "84")
  (if (and (= len 11) (/= (substr num len 1) " "))
    (progn
    (setvar "CLAYER" "N-CONF")
    ;(setvar "CECOLOR" "bylayer")
  ))
  (if (= (substr num len 1) "+")
    (progn
    (setvar "CLAYER" "N-EDI")
    ;(setvar "CECOLOR" "bylayer")
  ))
  
  (command "_text"
	   pt1
	   (* (atof num_h) scala)
	   (atof (angtos (atof num_ang) 0 4))
	   num
  )
  ;(setvar "CECOLOR" "bylayer")
  (setvar "CLAYER" "PART")

  (if (and (= len 11) (/= (substr num len 1) " "))
    (setvar "CLAYER" "CONFINE")
  )
  (if (= (substr num len 1) "+")
    (setvar "CLAYER" "EDI")
  )
  (setq pol_ins (read-line fp))
  (while (eq (substr pol_ins 1 1) " ")
    (setq pol_ins (substr pol_ins 2))
  )
  (setq pol_ins (atoi pol_ins))
  (setq vert (read-line fp))
  (while (eq (substr vert 1 1) " ")
    (setq vert (substr vert 2))
  )
  (setq vert (atoi vert))
  (repeat pol_ins
    (setq vert_ins (read-line fp))
    (while (eq (substr vert_ins 1 1) " ")
      (setq vert_ins (substr vert_ins 2))
    )
    (setq vert (- vert (atoi vert_ins)))
    (if	(or (= (getvar "CLAYER") "CONFINE") (= (getvar "CLAYER") "EDI"))
      (setq br_vert_ins (cons (atoi vert_ins) br_vert_ins))
    )
  )
  (setq ptlist nil)
  (repeat vert
    (setq pt1x (read-line fp))
    (while (eq (substr pt1x 1 1) " ")
      (setq pt1x (substr pt1x 2))
    )
    (setq pt1y (read-line fp))
    (while (eq (substr pt1y 1 1) " ")
      (setq pt1y (substr pt1y 2))
    )
    (setq pt1 (list (atof pt1x) (atof pt1y)))
    (setq ptlist (cons pt1 ptlist))
  )
  (setq ptlist (reverse ptlist))


  (if (or (= (getvar "CLAYER") "CONFINE") (= (getvar "CLAYER") "EDI"))
    (progn
      (setq i 1)
      (while (< i 2)
        (draw-pline-c ptlist)
        (setq i (+ i 1)) 
      )
    )
    (draw-pline-c ptlist)
  )



  (if (or (= (getvar "CLAYER") "CONFINE") (= (getvar "CLAYER") "EDI"))
    (progn
      (setq br_vert_ins (reverse br_vert_ins))
      (repeat pol_ins
	(setq ptlist nil)
	(setq vert (car br_vert_ins))
	(setq br_vert_ins (cdr br_vert_ins))
	(repeat	vert
	  (setq pt1x (read-line fp))
	  (while (eq (substr pt1x 1 1) " ")
	    (setq pt1x (substr pt1x 2))
	  )
	  (setq pt1y (read-line fp))
	  (while (eq (substr pt1y 1 1) " ")
	    (setq pt1y (substr pt1y 2))
	  )
	  (setq pt1 (list (atof pt1x) (atof pt1y)))
	  (setq ptlist (cons pt1 ptlist))
	)
	(setq ptlist (reverse ptlist))
	(draw-pline-c ptlist)
      )
    )
  )
)

(defun draw-txt	(la / num num_h num_ang pt1x pt1y pt1)
  (setq num (read-line fp))
  (if (= num "") (alert "PRAZEN TEXT, PROVERI TESTO"))
  (setq num (remove-space num))
  (setq num_h (read-line fp))
  (while (eq (substr num_h 1 1) " ")
    (setq num_h (substr num_h 2))
  )
  (if (and (/= num_h "25") (/= num_h "40") (/= num_h "90") (/= num_h "14"))
    (setq num_h "25"))
  (setq num_ang (read-line fp))
  (while (eq (substr num_ang 1 1) " ")
    (setq num_ang (substr num_ang 2))
  )
  (setq pt1x (read-line fp))
  (while (eq (substr pt1x 1 1) " ")
    (setq pt1x (substr pt1x 2))
  )
  (setq pt1y (read-line fp))
  (while (eq (substr pt1y 1 1) " ")
    (setq pt1y (substr pt1y 2))
  )
  (setq pt1 (list (atof pt1x) (atof pt1y)))
  (setvar "CLAYER" la)
  (if (eq num_h "0")
    (setq num_h "20")
  )
  (command "_text"
	   pt1
	   (* (atof num_h) scala)
	   (atof (angtos (atof num_ang) 0 4))
	   num
  )
)

(defun draw-sim	(la / name num_ang pt1x pt1y pt1)
  (setq name (read-line fp))
  (while (eq (substr name 1 1) " ")
    (setq name (substr name 2))
  )
  (setq num_ang (read-line fp))
  (while (eq (substr num_ang 1 1) " ")
    (setq num_ang (substr num_ang 2))
  )
  (setq pt1x (read-line fp))
  (while (eq (substr pt1x 1 1) " ")
    (setq pt1x (substr pt1x 2))
  )
  (setq pt1y (read-line fp))
  (while (eq (substr pt1y 1 1) " ")
    (setq pt1y (substr pt1y 2))
  )
  (setq pt1 (list (atof pt1x) (atof pt1y)))
  (setvar "CLAYER" la)
  (command "-insert"
	   name
	   pt1
	   (* 10 scala)
	   ""
	   (atof (angtos (atof num_ang) 0 4))
  )

)

(defun draw-line (la / tip vert ptlist pt1 pt1x pt1y)
  (setq tip (read-line fp))
  (while (eq (substr tip 1 1) " ")
    (setq tip (substr tip 2))
  )
  (while (eq (substr tip (strlen tip) 1) " ")
    (setq tip (substr tip 1 (- (strlen tip) 1)))
  )

  (setq vert (read-line fp))
  (while (eq (substr vert 1 1) " ")
    (setq vert (substr vert 2))
  )
  (setq vert (atoi vert))
  (setq ptlist nil)
  (repeat vert
    (setq pt1x (read-line fp))
    (while (eq (substr pt1x 1 1) " ")
      (setq pt1x (substr pt1x 2))
    )
    (setq pt1y (read-line fp))
    (while (eq (substr pt1y 1 1) " ")
      (setq pt1y (substr pt1y 2))
    )
    (setq pt1 (list (atof pt1x) (atof pt1y)))
    (setq ptlist (cons pt1 ptlist))
  )
  (setvar "CLAYER" la)
  (setvar "CELTYPE" tip)
  (setq ptlist (reverse ptlist))
  (draw-pline ptlist)
  (setvar "CELTYPE" "ByLayer")
)


(defun draw-div (la / vert ptlist pt1 pt1x pt1y)
  (setq vert (read-line fp))
  (while (eq (substr vert 1 1) " ")
    (setq vert (substr vert 2))
  )
  (setq vert (atoi vert))
  (setq ptlist nil)
  (repeat vert
    (setq pt1x (read-line fp))
    (while (eq (substr pt1x 1 1) " ")
      (setq pt1x (substr pt1x 2))
    )
    (setq pt1y (read-line fp))
    (while (eq (substr pt1y 1 1) " ")
      (setq pt1y (substr pt1y 2))
    )
    (setq pt1 (list (atof pt1x) (atof pt1y)))
    (setq ptlist (cons pt1 ptlist))
  )
  (setvar "CLAYER" la)
  (setq ptlist (reverse ptlist))
  (draw-pline ptlist)
)



(defun draw-fidu (la / name txt pt1x pt1y pt1 pt2 pt2x pt2y)
  (setq txt (read-line fp))
  (setq txt (remove-space txt))
  (setq name (read-line fp))
  (while (eq (substr name 1 1) " ")
    (setq name (substr name 2))
  )


  (setq pt1x (read-line fp))
  (while (eq (substr pt1x 1 1) " ")
    (setq pt1x (substr pt1x 2))
  )
  (setq pt1y (read-line fp))
  (while (eq (substr pt1y 1 1) " ")
    (setq pt1y (substr pt1y 2))
  )
  (setq pt1 (list (atof pt1x) (atof pt1y)))
  (setq pt2x (read-line fp))
  (while (eq (substr pt2x 1 1) " ")
    (setq pt2x (substr pt2x 2))
  )
  (setq pt2y (read-line fp))
  (while (eq (substr pt2y 1 1) " ")
    (setq pt2y (substr pt2y 2))
  )
  (setq pt2 (list (atof pt2x) (atof pt2y)))
  (setvar "CLAYER" la)
  (command "-insert" name pt1 (* 10 scala) "" 0)
  (command "_text" pt2 (* 14 scala) 0 txt)
  (command "_line" pt1 pt2 "")
)



(defun draw-lib	(/ vert ptlist pt1 pt1x pt1y)
  (read-line fp)
  (read-line fp)
  (setq vert (read-line fp))
  (while (eq (substr vert 1 1) " ")
    (setq vert (substr vert 2))
  )
  (setq vert (atoi vert))
  (setq ptlist nil)
  (repeat vert
    (setq pt1x (read-line fp))
    (while (eq (substr pt1x 1 1) " ")
      (setq pt1x (substr pt1x 2))
    )
    (setq pt1y (read-line fp))
    (while (eq (substr pt1y 1 1) " ")
      (setq pt1y (substr pt1y 2))
    )
    (setq pt1 (list (atof pt1x) (atof pt1y)))
    (setq ptlist (cons pt1 ptlist))
  )
  (setvar "CLAYER" "LIBRETTO")
  (setq ptlist (reverse ptlist))
  (draw-pline ptlist)
)

(defun draw-raster (/ ptlist pt1x pt1y pt1 name pt-text)
  (setq name (read-line fp))
  (setq name (remove-space name))
  (setq dwg-name (substr name 1 11))
  (setq dwg-name (strcat "C:\\cat\\etap0\\" dwg-name))
  (setq ptlist nil)
  (repeat 4
    (setq pt1x (read-line fp))
    (while (eq (substr pt1x 1 1) " ")
      (setq pt1x (substr pt1x 2))
    )
    (setq pt1y (read-line fp))
    (while (eq (substr pt1y 1 1) " ")
      (setq pt1y (substr pt1y 2))
    )
    (setq pt1 (list (atof pt1x) (atof pt1y)))
    (if	(= pt-text nil)
      (setq pt-text pt1)
    )
    (setq ptlist (cons pt1 ptlist))
  )
  (setvar "CLAYER" "RASTER")
  (command "_text" pt-text (* 20 scala) 0 name)
  (setq ptlist (reverse ptlist))
  (draw-pline-c ptlist)
)



(defun draw-cntr (la / num num_h num_ang pt1x pt1y pt1)
  (setq num (read-line fp))
  (setq num (remove-space num))
  (setq num_h (* 18 scala))
  (setq pt1x (read-line fp))
  (while (eq (substr pt1x 1 1) " ")
    (setq pt1x (substr pt1x 2))
  )
  (setq pt1y (read-line fp))
  (while (eq (substr pt1y 1 1) " ")
    (setq pt1y (substr pt1y 2))
  )
  (setq pt1 (list (atof pt1x) (atof pt1y)))
  (setvar "CLAYER" la)
  (command "_text"
	   pt1
	   num_h
	   0
	   num
  )
)

(defun c:change-colors ( / ss)
  (setq ss (ssget "X" (list (cons 0 "LINE") (cons 8 "L-PART"))))
  (if ss
    (command "chprop" ss "" "c" "161" "")
  )
  (setq ss (ssget "X" (list (cons 0 "LINE") (cons 8 "PART-EDI"))))
  (if ss
    (command "chprop" ss "" "c" "40" "")
  )
  (setq ss (ssget "X" (list (cons 0 "LINE") (cons 8 "L-EDI"))))
  (if ss
    (command "chprop" ss "" "c" "141" "")
  )  
	 
)


(defun cxf-start (/ ss i broi ent)
  (change-prop "TESTO,TESTO-OUT" "TEXT" 40 (* 1.8 scala))
  (change-prop "TESTO,TESTO-OUT" "TEXT" 8 "N-PART")
  (setq ss (ssget "X" (list (cons 8 "CONFINE,N-CONF"))))
  ;(if ss
  ;  (command "erase" ss "")
  ;)
  (setq ss (ssget "X" (list (cons 0 "LWPOLYLINE") (cons 8 "PART,EDI"))))
  (setvar "qaflags" 1)
  (if ss
    (command "explode" ss "")
  )
  (setvar "qaflags" 0)
  (change-prop "PART" "LINE" 8 "L-PART")
  (change-prop "EDI" "LINE" 8 "L-EDI")

  (change-prop "N-PART" "TEXT" 50 0)
  (setvar "CMDDIA" 0)
  (command "_ADEDWGCLEAN"	   "OBjects"   "Auto"	   "on"
	   "exit"      "Options"   "Edit"      "cluster"   "n"
	   "Undershoot"		   "n"	       "CRoss"	   "n"
	   "Dangle"    "n"	   "Short"     "y"	   "Pseudo"
	   "n"	       "DUp"	   "y"	       "Tolerance" "0.01"
	   "exit"      "exit"	   "Perform"
	  )
  (setvar "CMDDIA" 1)
)


(defun cxf-start-new (/ ss i broi ent)
;;  (change-prop "TESTO,TESTO-OUT" "TEXT" 40 (* 2.5 scala))   promenia visochinite pri greshka!!!!!!!!!
;;  (change-prop "N-PART" "TEXT" 40 (* 1.8 scala))
;;  (change-prop "N-EDI" "TEXT" 40 (* 1.8 scala))
  (setq ss (ssget "X" (list (cons 0 "LWPOLYLINE") (cons 8 "PART,EDI,CONFINE"))))
  (setvar "qaflags" 1)
  (if ss
    (command "explode" ss "")
  )
  (setvar "qaflags" 0)
  (change-prop "PART" "LINE" 8 "L-PART")
  (change-prop "EDI" "LINE" 8 "L-EDI")
  (change-prop "CONFINE" "LINE" 8 "L-CONFINE")

  ;(change-prop "N-PART" "TEXT" 50 0)
  (clear-la "L-PART")
  (clear-la "L-CONFINE")
  (clear-la "L-EDI")
  (clear-dup "L-PART" "L-CONFINE" "L-CONFINE")
  (clear-dup "L-EDI" "L-PART" "PART-EDI")
  (clear-dup "L-EDI" "L-CONFINE" "CONF-EDI")
)

(defun change-height-raster ( / ss)
      (change-prop "RASTER" "TEXT" 40 (* 15 scala))
)

(defun change-prop (la tip cod val / ss i broi ent)
  (setq ss (ssget "X" (list (cons 0 tip) (cons 8 la))))
  (setq i 0)
  (if ss
    (progn
      (setq broi (sslength ss))
      (while (< i broi)
	(setq ent (entget (ssname ss i)))
	(setq ent (subst (cons cod val) (assoc cod ent) ent))
	(entmod ent)
	(setq i (+ i 1))
      )
    )
  )
)



(defun c:cxf-i	(/ txt map la)
  (setvar "CMDECHO" 0)
  (command "-layer" "t" "*" "on" "*" "")
  (command "-osnap" "OFF")
  (command "snap" "OFF")
  (command "ortho" "OFF")
  (if (not dir) (setq dir "c:\\cat\\"))
  (while (= fp nil)
    (setq map (getfiled "Select a CXF file" dir "cxf" 4))
    (setq dir map)
    (setq fp (open map "r"))
  )
  (setq txt (read-line fp))
  (setq map (read-line fp))
  (setq map (remove-space map))
  (setq scala (read-line fp))

  (while (eq (substr scala 1 1) " ")
    (setq scala (substr scala 2))
  )
  (setq scala (* (atof scala) 0.0001))
  (setq txt (read-line fp))
  (setq txt (remove-space txt))
  (while (/= txt "EOF")

    (cond ((= txt "BORDO")
	   (draw-bordo)
	  )
	  ((= (substr txt 1 5) "TESTO")
	   (progn
	     (setq la (substr txt 1 5))
	     (if (= (substr txt 6 1) "\\")
	       (setq la "TESTO-OUT")
	     )
	     (draw-txt la)
	   )
	  )
	  ((= (substr txt 1 7) "SIMBOLO")
	   (progn
	     (setq la (substr txt 1 7))
	     (if (= (substr txt 8 1) "\\")
	       (setq la "SIMBOLO-OUT")
	     )
	     (draw-sim la)
	   )
	  )
	  ((= (substr txt 1 5) "LINEA")
	   (progn
	     (setq la (substr txt 1 5))
	     (if (= (substr txt 6 1) "\\")
	       (setq la "LINEA-OUT")
	     )
	     (draw-line la)
	   )
	  )
;;;;;	  ((= (substr txt 1 9) "DIVIDENTI")
;;;;	   (progn
;;;;	     (setq la (substr txt 1 9))
;;;;	     (draw-div la)
;;;;	   )
;;;;	  )
	  ((= (substr txt 1 9) "FIDUCIALE")
	   (progn
	     (setq la (substr txt 1 9))
	     (if (= (substr txt 10 1) "\\")
	       (setq la "FIDUCIALE-OUT")
	     )
	     (draw-fidu la)
	   )
	  )
	  ((= (substr txt 1 8) "LIBRETTO")
	   (draw-lib)
	  )
	  ((= (substr txt 1 18) "RIFERIMENTO_RASTER")
	   (draw-raster)
	  )
	  ((= (substr txt 1 9) "CENTROIDE")
	   (progn
	     (setq la "N-PART")
	     (draw-cntr la)
	   )
	  )	  
	  (t nil)
    )    
    (setq txt (read-line fp))
    (if	txt
      (setq txt (remove-space txt))
    )
  )
  (close fp)
  (setq fp nil)
  (setq scala (* scala 10))
;  (setvar "FILEDIA" 0)
;  (command "shell" "mkdir C:\\cat\\etap0")
;  (command "saveas" "" dwg-name)
;  (setvar "FILEDIA" 1)
;  (cxf-start)
;  (c:del-short)
  (command "zoom" "e")
  (setvar "CMDECHO" 1)
)

(defun c:cxf-a	(/ txt map la)
  (setvar "CMDECHO" 0)
  (command "-layer" "t" "*" "on" "*" "")
  (command "color" "cyan")
  (command "-osnap" "OFF")
  (command "snap" "OFF")
  (command "ortho" "OFF")
  (if (not dir) (setq dir "c:\\cat\\"))
  (while (= fp nil)
    (setq map (getfiled "Select a CXF file" dir "cxf" 4))
    (setq dir map)
    (setq fp (open map "r"))
  )
  (setq txt (read-line fp))
  (setq map (read-line fp))
  (setq map (remove-space map))
  (setq scala (read-line fp))

  (while (eq (substr scala 1 1) " ")
    (setq scala (substr scala 2))
  )
  (setq scala (* (atof scala) 0.0001))
  (setq txt (read-line fp))
  (setq txt (remove-space txt))
  (while (/= txt "EOF")

    (cond ((= txt "BORDO")
	   (draw-bordo)
	  )
	  ((= (substr txt 1 5) "TESTO")
	   (progn
	     (setq la (substr txt 1 5))
	     (if (= (substr txt 6 1) "\\")
	       (setq la "TESTO-OUT")
	     )
	     (draw-txt la)
	   )
	  )
	  ((= (substr txt 1 7) "SIMBOLO")
	   (progn
	     (setq la (substr txt 1 7))
	     (if (= (substr txt 8 1) "\\")
	       (setq la "SIMBOLO-OUT")
	     )
	     (draw-sim la)
	   )
	  )
	  ((= (substr txt 1 5) "LINEA")
	   (progn
	     (setq la (substr txt 1 5))
	     (if (= (substr txt 6 1) "\\")
	       (setq la "LINEA-OUT")
	     )
	     (draw-line la)
	   )
	  )
;;;;;	  ((= (substr txt 1 9) "DIVIDENTI")
;;;;	   (progn
;;;;	     (setq la (substr txt 1 9))
;;;;	     (draw-div la)
;;;;	   )
;;;;	  )
	  ((= (substr txt 1 9) "FIDUCIALE")
	   (progn
	     (setq la (substr txt 1 9))
	     (if (= (substr txt 10 1) "\\")
	       (setq la "FIDUCIALE-OUT")
	     )
	     (draw-fidu la)
	   )
	  )
	  ((= (substr txt 1 8) "LIBRETTO")
	   (draw-lib)
	  )
	  ((= (substr txt 1 18) "RIFERIMENTO_RASTER")
	   (draw-raster)
	  )
	  ((= (substr txt 1 9) "CENTROIDE")
	   (progn
	     (setq la "N-PART")
	     (draw-cntr la)
	   )
	  )	  
	  (t nil)
    )    
    (setq txt (read-line fp))
    (if	txt
      (setq txt (remove-space txt))
    )
  )
  (close fp)
  (setq fp nil)
  (setq scala (* scala 10))
;  (setvar "FILEDIA" 0)
;  (command "shell" "mkdir C:\\cat\\etap0")
;  (command "saveas" "" dwg-name)
;  (setvar "FILEDIA" 1)
;  (cxf-start)
;  (c:del-short)
  (command "zoom" "e")
  (setvar "CMDECHO" 1)
  (command "color" "bylayer")
)


(defun clear-dup (la1 la2 la-new / ss1 ss2 broi1 broi2 i1 i2 a obj1 )
  (setq ss1 (ssget "X" (list (cons 0 "LINE") (cons 8 la1))))
  (setq ss2 (ssget "X" (list (cons 0 "LINE") (cons 8 la2))))
  (if (and ss1 ss2)
    (progn
      (setq i1 0 broi1 (sslength ss1))
      (while (< i1 broi1)
	(setq ent1 (entget (ssname ss1 i1)))
	(setq obj1 (ssname ss1 i1))
	(setq i2 0 broi2 (sslength ss2))
	(while (and (/= a 1) (< i2 broi2))
	  (setq ent2 (entget (ssname ss2 i2)))
	  (setq a (sravni-line ent1 ent2))
	  (if (= a 1)
	    (progn
	      (command ".erase" obj1 "")
	      (setq ent2 (subst (cons 8 la-new) (assoc 8 ent2) ent2))
              (entmod ent2)
	    )
	  )
	  (setq i2 (+ i2 1))
	)
	(setq i1 (+ i1 1))
	(setq a 0)
      )
    )
    (princ (strcat "\nLipsvat linii" la1))
  )
)

(defun clear-la ( la / ss)
  (setvar "CMDDIA" 0)
  (setq ss (ssget "X" (list (cons 0 "LINE") (cons 8 la))))
  (if ss
  (command "_ADEDWGCLEAN"	   "OBjects"   "Filter"	la "Auto"  "on"
	   "exit"      "Options"   "Edit"      "cluster"   "n"
	   "Undershoot"		   "n"	       "CRoss"	   "n"
	   "Dangle"    "n"	   "Short"     "y"	   "Pseudo"
	   "n"	       "DUp"	   "y"	       "Tolerance" "0.01"
	   "exit"      "exit"	   "Perform"
	  )
  )
  (setvar "CMDDIA" 1)

)

(defun sravni-line ( ent1 ent2 / x1 x2 y1 y2 a )
  (setq x1 (cdr (assoc 10 ent1)))
  (setq y1 (cdr (assoc 11 ent1)))
  (setq x2 (cdr (assoc 10 ent2)))
  (setq y2 (cdr (assoc 11 ent2)))
  (if (or (and (equal x1 x2 0.01) (equal y1 y2 0.01)) (and (equal x1 y2 0.01) (equal x2 y1 0.01)))
    (setq a 1)
    (setq a 0))
  
)
